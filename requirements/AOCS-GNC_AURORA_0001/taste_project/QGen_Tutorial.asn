------------------------------------------------------------------------------
--                                                                          --
--                         Q G e n   T u t o r i a l                        --
--                                                                          --
--                         Dataview ASN.1 definition                        --
--                                                                          --
--          Copyright (C) 2022 Universidad Politécnica de Madrid            --
--                                                                          --
-- This is free software;  you can redistribute it  and/or modify it  under --
-- terms of the  GNU General Public License as published  by the Free Soft- --
-- ware  Foundation;  either version 3,  or (at your option) any later ver- --
-- sion.  This software is distributed in the hope  that it will be useful, --
-- but WITHOUT ANY WARRANTY;  without even the implied warranty of MERCHAN- --
-- TABILITY or FITNESS FOR A PARTICULAR PURPOSE. See the GNU General Public --
-- License for  more details.  You should have  received  a copy of the GNU --
-- General  Public  License  distributed  with  this  software;   see  file --
-- COPYING3.  If not, go to http://www.gnu.org/licenses for a complete copy --
-- of the license.                                                          --
--                                                                          --
------------------------------------------------------------------------------

QGEN-TUTORIAL-DATAVIEW DEFINITIONS ::=
BEGIN
    -------------------------
    -- Reusable data types --
    -------------------------
    T-Float      ::= REAL (-3.4e+38 .. 3.4e+38)
    T-UInteger32 ::= INTEGER (0 .. 4294967295)

    -------------------------------------------
    -- Data types used for the ACS component --
    -------------------------------------------
    -- Input types:
    -- 5 x 3 (3 magnetometers, 5 samples each)
    T-B-b-T      ::= SEQUENCE (SIZE(15)) OF T-Float
    T-Omega      ::= SEQUENCE (SIZE(3))  OF T-Float
    T-MT-Working ::= SEQUENCE (SIZE(3))  OF T-Float

    -- Output types:
    T-Control    ::= SEQUENCE (SIZE(3))  OF T-Float

    -- GUI types
    T-Telecommand ::= CHOICE
    {
        m-start   INTEGER(0 .. 1),
        m-pause   INTEGER(0 .. 1),
        m-stop    INTEGER(0 .. 1),
        m-restart INTEGER(0 .. 1)
    }

    T-Telemetry  ::= SEQUENCE
    {
        m-sensors T-B-b-T,
        m-control T-Control,
        m-step    T-UInteger32
    }

END
