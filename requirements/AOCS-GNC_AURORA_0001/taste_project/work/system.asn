-- Dataview generated on-the-fly providing information on the system
-- and made available to the user code.
System-Dataview DEFINITIONS ::=
BEGIN

   -- Range of PID - type can be used to size arrays of PID type
   PID-Range ::= INTEGER(0..4)

   -- List of functions (instances) present in the system
   PID ::= ENUMERATED {
       acs-algorithm,
       
       mmi,
       
       measurer-and-actuator,
       
       simulated-acs-hw,
       
       
       env
   }

END
